module demo {
    yang-version 1.1;
    namespace "urn:opendaylight:params:xml:ns:yang:demo";
    prefix "demo";

    revision "2017-08-30" { // TODO change revision to date of model creation
        description "Initial revision of demo model";
    }
    rpc hello-world {
        input {
            leaf name{
                type string;
            }
        }
        output {
            leaf greeting {
                type string;
            }
        }
    }
    container greeting-registry{
        list greeting-registry-entry{
            key "name";
            leaf name {
                type string;
            }
            leaf greeting {
                type string;
            }
        }
    }
}
